module restconf-example {
  namespace "http://example.org/example-last-modified";
  prefix "ex";

  import openwrt-uci-extension {
    prefix uci;
  }

  typedef grade {
    type uint8 {
      range "0..100";
    }
  }

  typedef email {
    type string {
      pattern "[A-Za-z0-9]*@university.de";
    }
  }

  grouping instructor-data {
    leaf name {
      uci:option "name";
      type string;
    }
    leaf email {
      uci:option "email";
      type email;
    }
  }

  uci:package "restconf-example";
  container course {
    uci:section-name "course";
    uci:section "course";

    leaf name {
      uci:option "name";
      type string;
      description "name of the course";
    }

    leaf-list instructors {
      uci:option "instructors";
      type string;
      description "list of names of instructors";
    }

    leaf semester {
      uci:option "semester";
      type uint8 {
        range "1..6";
      }
    }

    list students {
      uci:section "student";
      uci:leaf-as-name "lastname";
      uci:leaf-as-type "students";

      key "firstname lastname age";
      leaf firstname {
        uci:option "firstname";
        type string;
      }

      leaf lastname {
        uci:option "lastname";
        type string;
      }

      leaf age {
        uci:option "age";
        type uint8 {
          range "0..120";
        }
      }

      leaf major {
        uci:option "major";
        type string {
          pattern "(CS|IMS)";
        }
      }

      leaf grade {
        uci:option "grade";
        type grade;
      }

      list option {
        uci:section "options";
        uci:leaf-as-name "id";
        uci:leaf-as-type "student_options";

        key "id";

        leaf id {
          uci:option "id";
          type string;
        }

        leaf name {
          uci:option "name";
          type string;
        }
      }
    }

    container instructor {
      uci:section-name "instructor";
      uci:section "instructor";

      leaf name {
        uci:option "name";
        type string;
      }

      leaf email {
        uci:option "email";
        type email;
      }
    }
  }
}
